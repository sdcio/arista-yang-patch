module sdcio-netinst-deviations {
  namespace "http://sdcio.dev/yang/openconfig/network-instances/deviations";
  prefix sdcio-network-instances-deviations;

  import openconfig-network-instance {
    prefix oc-netinst;
  }
  import openconfig-network-instance-types {
    prefix oc-ni-types;
  }
  import openconfig-extensions {
    prefix oc-ext;
  }
  import openconfig-vlan-types {
    prefix oc-vlan-types;
  }

  organization
    "Schema Driven Configuration";
  contact
    "https://github.com/sdcio";
  description
    "This module contains OpenConfig Network Instances deviations in Arista EOS, in SDCIO";

  oc-ext:openconfig-version "1.0.0";

  revision 2025-10-02 {
    description
      "Initial Release, convert the subinterface index leafref to a value.";
    reference
      "1.0.0";
  }

  deviation "/oc-netinst:network-instances/oc-netinst:network-instance/oc-netinst:mpls" {
    description
      "MPLS is only supported in the default network instance.";
    deviate delete {
      must "../config/type = 'DEFAULT_INSTANCE'";
    }
    deviate add {
      must "../config/type = 'oc-ni-types:DEFAULT_INSTANCE'";
    }
  }

}
