module sdcio-acl-deviations {
  namespace "http://sdcio.dev/yang/openconfig/acl/deviations";
  prefix sdcio-acl-deviations;

  import openconfig-inet-types {
    prefix oc-inet;
  }
  import openconfig-acl {
    prefix oc-acl;
  }
  import openconfig-packet-match-types {
    prefix oc-pkt-match-types;
  }
  import openconfig-extensions {
    prefix oc-ext;
  }

  organization
    "Schema Driven Configuration";
  contact
    "https://github.com/sdcio";
  description
    "This module contains OpenConfig ACL deviations for Arista EOS. in SDCIO";

  oc-ext:openconfig-version "1.0.0";

  revision 2024-11-07 {
    description
      "Initial Release, modify oc-acl:acl-entry/oc-acl:sequence-id leafref in ingress-acl-sets and egress-acl-sets as it's referring to a deleted path by arista's deviations";
    reference
      "1.0.0";
  }
  deviation "/oc-acl:acl/oc-acl:interfaces/oc-acl:interface/oc-acl:ingress-acl-sets/oc-acl:ingress-acl-set/oc-acl:acl-entries/oc-acl:acl-entry/oc-acl:sequence-id" {
    description
      "Per-interface ACL state is not supported in EOS";
    deviate replace {
      type leafref {
        path "/oc-acl:acl/oc-acl:acl-sets/" +
          "oc-acl:acl-set[oc-acl:name=current()/../../../../set-name]" +
          "[oc-acl:type=current()/../../../../type]/" +
          "oc-acl:acl-entries/oc-acl:acl-entry/oc-acl:sequence-id";
      }
    }
  }

  deviation "/oc-acl:acl/oc-acl:interfaces/oc-acl:interface/oc-acl:egress-acl-sets/oc-acl:egress-acl-set/oc-acl:acl-entries/oc-acl:acl-entry/oc-acl:sequence-id" {
    description
      "Per-interface ACL state is not supported in EOS";
    deviate replace {
      type leafref {
        path "/oc-acl:acl/oc-acl:acl-sets/" +
          "oc-acl:acl-set[oc-acl:name=current()/../../../../set-name]" +
          "[oc-acl:type=current()/../../../../type]/" +
          "oc-acl:acl-entries/oc-acl:acl-entry/oc-acl:sequence-id";
      }
    }
  }
}
