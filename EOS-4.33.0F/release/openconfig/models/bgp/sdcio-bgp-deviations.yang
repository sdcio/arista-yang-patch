module sdcio-bgp-deviations {
  namespace "http://sdcio.dev/yang/openconfig/bgp/deviations";
  prefix sdcio-bgp-deviations;

  import openconfig-network-instance {
    prefix oc-netinst;
  }
  import openconfig-policy-types {
    prefix oc-pol-types;
  }
  import openconfig-extensions {
    prefix oc-ext;
  }
  import openconfig-bgp-types {
    prefix oc-bgp-types;
  }
  organization
    "Schema Driven Configuration";
  contact
    "https://github.com/sdcio";
  description
    "This module contains OpenConfig BGP deviations in Arista EOS, in SDCIO";

  oc-ext:openconfig-version "1.0.0";

  revision 2025-10-02 {
    description
      "Initial Release, convert the subinterface index leafref to a value.";
    reference
      "1.0.0";
  }

  deviation "/oc-netinst:network-instances/oc-netinst:network-instance/oc-netinst:protocols/oc-netinst:protocol/oc-netinst:bgp/oc-netinst:global/oc-netinst:afi-safis/oc-netinst:afi-safi/oc-netinst:config/oc-netinst:afi-safi-name" {
    description
      "L2VPN_EVPN, IPV4_UNICAST, IPV6_UNICAST, IPV4_MULTICAST, IPV6_MULTICAST, L3VPN_IPV4_UNICAST and L3VPN_IPV6_UNICAST are the only AFI-SAFIs type supported in EOS";
    deviate delete {
      must "../afi-safi-name = 'IPV4_UNICAST' or ../afi-safi-name = 'IPV6_UNICAST' or ../afi-safi-name = 'IPV4_MULTICAST' or ../afi-safi-name = 'IPV6_MULTICAST' or ../afi-safi-name = 'L2VPN_EVPN' or ../afi-safi-name = 'L3VPN_IPV4_UNICAST' or ../afi-safi-name = 'L3VPN_IPV6_UNICAST'" {
        error-message "L2VPN_EVPN, IPV4_UNICAST, IPV6_UNICAST, IPV4_MULTICAST, IPV6_MULTICAST, L3VPN_IPV4_UNICAST and L3VPN_IPV6_UNICAST are the only AFI-SAFIs type supported in EOS";
      }
    }
    deviate add {
      must "../afi-safi-name = 'oc-bgp-types:IPV4_UNICAST' or ../afi-safi-name = 'oc-bgp-types:IPV6_UNICAST' or ../afi-safi-name = 'oc-bgp-types:IPV4_MULTICAST' or ../afi-safi-name = 'oc-bgp-types:IPV6_MULTICAST' or ../afi-safi-name = 'oc-bgp-types:L2VPN_EVPN' or ../afi-safi-name = 'oc-bgp-types:L3VPN_IPV4_UNICAST' or ../afi-safi-name = 'oc-bgp-types:L3VPN_IPV6_UNICAST'" {
        error-message "L2VPN_EVPN, IPV4_UNICAST, IPV6_UNICAST, IPV4_MULTICAST, IPV6_MULTICAST, L3VPN_IPV4_UNICAST and L3VPN_IPV6_UNICAST are the only AFI-SAFIs type supported in EOS";
      }
    }
  }
}
