module sdcio-if-ip-deviations {
  namespace "http://sdcio.dev/yang/openconfig/interfaces/ip/deviations";
  prefix sdcio-if-ip-deviations;

  import openconfig-inet-types { prefix oc-inet; }
  import openconfig-interfaces { prefix oc-if; }
  import openconfig-if-ip { prefix oc-ip; }
  import openconfig-vlan { prefix oc-vlan; }
  import openconfig-yang-types { prefix oc-yang; }
  import openconfig-extensions { prefix oc-ext; }

  organization
    "Schema Driven Configuration";
  contact
    "https://github.com/sdcio";
  description
    "This module contains OpenConfig interfaces ip deviations for Arista EOS. in SDCIO";

  oc-ext:openconfig-version "1.0.0";

  revision 2024-12-03 {
    description
      "Initial Release, make sure link-layer-address is not a mandatory flag for staticly configured neighbors.";
    reference
      "1.0.0";
  }

  deviation "/oc-if:interfaces/oc-if:interface/oc-if:subinterfaces/oc-if:subinterface/oc-ip:ipv4/oc-ip:neighbors/oc-ip:neighbor/oc-ip:config/oc-ip:link-layer-address" {
    description "Arista is populating dynamically learned neighbors as static configured neighbors. However the YANG model defines the link-layer-address is a mandatory statement. This deviation is required until Arista fixes the data returned from box. Impact: static arp/ND via SDCIO might not be 100% valid.";
    deviate delete {
      mandatory true;
    }
  }
  deviation "/oc-if:interfaces/oc-if:interface/oc-if:subinterfaces/oc-if:subinterface/oc-ip:ipv6/oc-ip:neighbors/oc-ip:neighbor/oc-ip:config/oc-ip:link-layer-address" {
    description "Arista is populating dynamically learned neighbors as static configured neighbors. However the YANG model defines the link-layer-address is a mandatory statement. This deviation is required until Arista fixes the data returned from box. Impact: static arp/ND via SDCIO might not be 100% valid.";
    deviate delete {
      mandatory true;
    }
  }
}
